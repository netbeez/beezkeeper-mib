-- *****************************************************************
-- NETBEEZ-BEEZKEEPER-MIB
--  NetBeez SNMP traps MIB
--
-- April, 2017 Stefano Gridelli, Panickos Neophytou, Joshua Sarver
--     Revised July 19, 2017 (3.1)
--     Revised September 20, 2017 (3.2)
--     Revised November 8, 2017 (3.3)
--     Revised October 18, 2026 (4.0)
--
-- Copyright (c) 2017-2026 by Netbeez, Inc.
-- All rights reserved.
-- *****************************************************************

NETBEEZ-BEEZKEEPER-MIB DEFINITIONS ::= BEGIN

IMPORTS
	MODULE-IDENTITY, enterprises,
	OBJECT-TYPE, NOTIFICATION-TYPE
		FROM SNMPv2-SMI
	DateAndTime
		FROM SNMPv2-TC
    OBJECT-GROUP, NOTIFICATION-GROUP
        FROM SNMPv2-CONF;

netbeez	MODULE-IDENTITY
		LAST-UPDATED "202610180000Z"
		ORGANIZATION "NetBeez, Inc."
		CONTACT-INFO
			"NetBeez, Inc.
			netbeez.net

			Postal: NetBeez, Inc.
			5124B Penn Avenue
			Pittsburgh, PA 15224
			USA

			Phone:	+1 844-NET-BEEZ
			EMail:	support@netbeez.net"

		DESCRIPTION
			"This MIB contains definition of the SNMP Traps
			associated to alerts sent by the NetBeez BeezKeeper"

		REVISION
			"202610180000Z"

		DESCRIPTION
			"Version 4.0. Identifiers of alerts, agents, incident events,
			incidents, and incident source objects are UUID strings
			(OCTET STRING). Incident opening and closing events each have
			their own event UUID, and incidentID matches the opening
			incident event's UUID. Timestamps use DateAndTime in UTC
			(11-octet form). Moved incidentEventNotification under
			nbAlertNotifications ({ nbAlertNotifications 3 }). Added
			scheduled and path analysis test types to testType."

		REVISION
			"201704200000Z"

		DESCRIPTION
			"First revision that includes only the alerts subtree"

	::= { enterprises 44523 }

beezKeeperMIB	OBJECT IDENTIFIER ::= { netbeez 1 }

-- groups in BeezKeeperMIB

nbAlerts		OBJECT IDENTIFIER ::= { beezKeeperMIB 1 }

nbAlertNotifications    OBJECT IDENTIFIER ::= { beezKeeperMIB 0 }

nbGroups OBJECT IDENTIFIER ::= { beezKeeperMIB 2 }

nbIncidents OBJECT IDENTIFIER ::= { beezKeeperMIB 4 }

nbIncidentNotifications OBJECT IDENTIFIER ::= { beezKeeperMIB 5 }

-- Groups of objects
beezAlertStatusGroup OBJECT-GROUP
    OBJECTS { beezAlertID, beezAlertType, beezSourceAlertID, beezAlertTimestamp, beezName, beezID, beezAlertMessage, beezAlertSeverity }
    STATUS  current
    DESCRIPTION
            "A collection of objects providing basic instrumentation and
            control of an SNMPv2 entity."
    ::= { nbGroups 1 }

testAlertStatusGroup OBJECT-GROUP
    OBJECTS { testAlertID, testType, testAlertSeverity, testSourceAlertID, testAlertTimestamp, testBeezName, testBeezID, testTargetName, testAlertMessage, testTargetDisplayName }
    STATUS  current
    DESCRIPTION
            "A collection of objects providing basic instrumentation and
            control of an SNMPv2 entity."
    ::= { nbGroups 2 }

nbAlertNotificationsGroup NOTIFICATION-GROUP
    NOTIFICATIONS { beezAlertNotification, testAlertNotification }
    STATUS        current
    DESCRIPTION
       "The basic notifications implemented by an SNMP entity
        supporting command responder applications."
    ::= { nbGroups 3 }

nbIncidentEventGroup OBJECT-GROUP
    OBJECTS { 	incidentEventID,
        incidentID,
        incidentEventMessage,
        incidentEventTimestamp,
        incidentSourceObjectType,
        incidentSourceObjectID,
        incidentSourceObjectName,
        incidentEventType
    }
    STATUS  current
    DESCRIPTION
            "A collection of objects providing basic instrumentation and
            control of an SNMPv2 entity for Incidents."
    ::= { nbGroups 4 }

nbIncidentNotificationsGroup NOTIFICATION-GROUP
    NOTIFICATIONS   { incidentEventNotification }
    STATUS          current
    DESCRIPTION
        "This notification group includes the event notifications that the BeezKeeper produces in regards to incidents
        triggered on the Agents or the Targets."
    ::= { nbGroups 5 }


-- objects

beezAlerts	OBJECT IDENTIFIER ::= { nbAlerts 1 }
testAlerts	OBJECT IDENTIFIER ::= { nbAlerts 2 }

beezStatusAlertTable	OBJECT-TYPE
	SYNTAX		SEQUENCE OF BeezStatusAlertEntry
	MAX-ACCESS	not-accessible
	STATUS		current
	DESCRIPTION
	  "This is the data structure associated to
	  alerts triggered by the NetBeez BeezKeeper."
	::= { beezAlerts 1 }

beezStatusAlertEntry	OBJECT-TYPE
	SYNTAX		BeezStatusAlertEntry
	MAX-ACCESS	not-accessible
	STATUS		current
	DESCRIPTION
	  "This is the data structure associated to
	  alerts triggered by the NetBeez BeezKeeper."
	INDEX	{ beezAlertID }
	::= { beezStatusAlertTable 1 }

BeezStatusAlertEntry	::= SEQUENCE	{
	beezAlertID		OCTET STRING,
	beezAlertType		INTEGER,
	beezAlertSeverity INTEGER,
	beezSourceAlertID	OCTET STRING,
	beezAlertTimestamp	DateAndTime,
	beezName		OCTET STRING,
	beezID			OCTET STRING,
	beezAlertMessage	OCTET STRING
	}

beezAlertID	OBJECT-TYPE
	SYNTAX		OCTET STRING (SIZE (0..255))
	MAX-ACCESS	read-only
	STATUS		current
	DESCRIPTION
	  "The UUID of the alert event being sent; this
	  identifier can be used to correlate cleared alerts
	  with raised ones."
	::= { beezStatusAlertEntry 1 }

beezAlertType	OBJECT-TYPE
	SYNTAX		INTEGER {
		beezReachabilityAlert (1),
		beez80211 (2)
	}
	MAX-ACCESS	read-only
	STATUS		current
	DESCRIPTION
	  "The type of agent alert being sent (reachability or 802.11)."
	::= { beezStatusAlertEntry 2 }

beezAlertSeverity	OBJECT-TYPE
	SYNTAX		INTEGER {
		statusDown (1),
		statusUp (6)
	}
	MAX-ACCESS	read-only
	STATUS		current
	DESCRIPTION
	  "The severity of the agent alert being sent."
	::= { beezStatusAlertEntry 8 }

beezSourceAlertID	OBJECT-TYPE
	SYNTAX		OCTET STRING
	MAX-ACCESS	read-only
	STATUS		current
	DESCRIPTION
	  "The UUID of the alert event originally raised.
	  For an opening alert event, this is the same as
	  beezAlertID."
	::= { beezStatusAlertEntry 3 }

beezAlertTimestamp	OBJECT-TYPE
	SYNTAX		DateAndTime
	MAX-ACCESS	read-only
	STATUS		current
	DESCRIPTION
	  "The UTC time when the alert event occurred, encoded as the
	  11-octet DateAndTime form (year through UTC offset, with Zulu
	  direction '+', hours from UTC 0, minutes from UTC 0)."
	::= { beezStatusAlertEntry 4 }

beezName	OBJECT-TYPE
	SYNTAX		OCTET STRING
	MAX-ACCESS	read-only
	STATUS		current
	DESCRIPTION
	  "The name of the beez that has triggered the
	  alert."
	::= { beezStatusAlertEntry 5 }

beezID	OBJECT-TYPE
	SYNTAX		OCTET STRING
	MAX-ACCESS	read-only
	STATUS		current
	DESCRIPTION
	  "The UUID of the beez that has triggered the
	  alert."
	::= { beezStatusAlertEntry 6 }

beezAlertMessage	OBJECT-TYPE
	SYNTAX		OCTET STRING
	MAX-ACCESS	read-only
	STATUS		current
	DESCRIPTION
	  "The actual message that describe the type of alert
	  raised or cleared."
	::= { beezStatusAlertEntry 7 }

--- TESTS alerts

testStatusAlertTable	OBJECT-TYPE
	SYNTAX		SEQUENCE OF TestStatusAlertEntry
	MAX-ACCESS	not-accessible
	STATUS		current
	DESCRIPTION
	  "This is the data structure associated to
	  alerts triggered by the NetBeez BeezKeeper."
	::= { testAlerts 1 }

testStatusAlertEntry	OBJECT-TYPE
	SYNTAX		TestStatusAlertEntry
	MAX-ACCESS	not-accessible
	STATUS		current
	DESCRIPTION
	  "This is the data structure associated to
	  alerts triggered by the NetBeez BeezKeeper."
	INDEX	{ testAlertID }
	::= { testStatusAlertTable 1 }

TestStatusAlertEntry	::= SEQUENCE	{
	testAlertID		OCTET STRING,
	testType		INTEGER,
	testAlertSeverity	INTEGER,
	testSourceAlertID	OCTET STRING,
	testAlertTimestamp	DateAndTime,
	testBeezName		OCTET STRING,
	testBeezID		OCTET STRING,
	testTargetName		OCTET STRING,
	testAlertMessage	OCTET STRING,
	testTargetDisplayName  OCTET STRING
	}

testAlertID	OBJECT-TYPE
	SYNTAX		OCTET STRING (SIZE (0..255))
	MAX-ACCESS	read-only
	STATUS		current
	DESCRIPTION
	  "The UUID of the alert event being sent; this
	  identifier can be used to correlate cleared alerts
	  with raised ones."
	::= { testStatusAlertEntry 1 }

testType	OBJECT-TYPE
	SYNTAX		INTEGER {
		pingTest (1),
		dnsTest (2),
		httpTest (3),
		tracerouteTest (4),
		iperfTest (5),
		networkSpeedTest (7),
		voipTest (8),
		pathAnalysisTest (9),
		packetCaptureTest (10),
		customCommandTest (11)
	}
	MAX-ACCESS	read-only
	STATUS		current
	DESCRIPTION
	  "The ID of the test type being sent."
	::= { testStatusAlertEntry 2 }

testAlertSeverity		OBJECT-TYPE
	SYNTAX		INTEGER {
		testAlertDown (1),
		testAlertPerformance (4),
		testAlertCleared (6)
	}
	MAX-ACCESS	read-only
	STATUS		current
	DESCRIPTION
	  "The severity of the test alert being sent."
	::= { testStatusAlertEntry 3 }

testSourceAlertID	OBJECT-TYPE
	SYNTAX		OCTET STRING
	MAX-ACCESS	read-only
	STATUS		current
	DESCRIPTION
	  "The UUID of the alert event originally raised.
	  For an opening alert event, this is the same as
	  testAlertID."
	::= { testStatusAlertEntry 4 }

testAlertTimestamp	OBJECT-TYPE
	SYNTAX		DateAndTime
	MAX-ACCESS	read-only
	STATUS		current
	DESCRIPTION
	  "The UTC time when the alert event occurred, encoded as the
	  11-octet DateAndTime form (year through UTC offset, with Zulu
	  direction '+', hours from UTC 0, minutes from UTC 0)."
	::= { testStatusAlertEntry 5 }

testBeezName	OBJECT-TYPE
	SYNTAX		OCTET STRING
	MAX-ACCESS	read-only
	STATUS		current
	DESCRIPTION
	  "The name of the beez that has triggered the
	  alert."
	::= { testStatusAlertEntry 6 }

testBeezID	OBJECT-TYPE
	SYNTAX		OCTET STRING
	MAX-ACCESS	read-only
	STATUS		current
	DESCRIPTION
	  "The UUID of the beez that has triggered the
	  alert."
	::= { testStatusAlertEntry 7 }

testTargetName	OBJECT-TYPE
	SYNTAX		OCTET STRING
	MAX-ACCESS	read-only
	STATUS		current
	DESCRIPTION
	  "If applicable, the name of the destination of the test
	  that has triggered the alert."
	::= { testStatusAlertEntry 8 }

testAlertMessage	OBJECT-TYPE
	SYNTAX		OCTET STRING
	MAX-ACCESS	read-only
	STATUS		current
	DESCRIPTION
	  "The actual message that describe the type of alert
	  raised or cleared."
	::= { testStatusAlertEntry 9 }

testTargetDisplayName	OBJECT-TYPE
	SYNTAX		OCTET STRING
	MAX-ACCESS	read-only
	STATUS		current
	DESCRIPTION
	  "If applicable, the display name of the destination of the test
	  that has triggered the alert, as it appear on the dashboard."
	::= { testStatusAlertEntry 10 }

-- Incident Event Object-Types

incidentEvents   OBJECT IDENTIFIER ::= { nbIncidents 1 }

incidentEventsTable	OBJECT-TYPE
	SYNTAX		SEQUENCE OF IncidentEventEntry
	MAX-ACCESS	not-accessible
	STATUS		current
	DESCRIPTION
	  "This is the data structure associated to
	  alerts triggered by the NetBeez BeezKeeper."
	::= { incidentEvents 1 }

incidentEventEntry	OBJECT-TYPE
	SYNTAX		IncidentEventEntry
	MAX-ACCESS	not-accessible
	STATUS		current
	DESCRIPTION
	  "This is the data structure associated to incidents triggered by the NetBeez BeezKeeper. Each entry here
	  corresponds to an event related to an incident"
	INDEX	{ incidentEventID }
	::= { incidentEventsTable 1 }

IncidentEventEntry	::= SEQUENCE	{
	incidentEventID		OCTET STRING,
	incidentID		    OCTET STRING,
	incidentEventMessage	OCTET STRING,
	incidentEventTimestamp	DateAndTime,
	incidentSourceObjectType    OCTET STRING,
	incidentSourceObjectID		OCTET STRING,
	incidentSourceObjectName    OCTET STRING,
	incidentEventType		    OCTET STRING
}


incidentEventID	OBJECT-TYPE
	SYNTAX		OCTET STRING (SIZE (0..255))
	MAX-ACCESS	read-only
	STATUS		current
	DESCRIPTION
	    "The UUID of the incident event (the opening or closing event ID)."
	::= { incidentEventEntry 1 }

incidentID      OBJECT-TYPE
    SYNTAX      OCTET STRING
    MAX-ACCESS	read-only
    STATUS		current
    DESCRIPTION
        "The UUID of the incident that a message is reporting on (the opening incident event's ID)."
    ::= { incidentEventEntry 2 }

incidentEventMessage	OBJECT-TYPE
	SYNTAX		OCTET STRING
	MAX-ACCESS	read-only
	STATUS		current
	DESCRIPTION
	    "The incident message describing the incident event."
	::= { incidentEventEntry 3 }

incidentEventTimestamp	OBJECT-TYPE
    SYNTAX      DateAndTime
    MAX-ACCESS	read-only
    STATUS		current
    DESCRIPTION
        "The UTC time when the incident event occurred, encoded as the
        11-octet DateAndTime form (year through UTC offset, with Zulu
        direction '+', hours from UTC 0, minutes from UTC 0)."
    ::= { incidentEventEntry 4 }

incidentSourceObjectType	OBJECT-TYPE
    SYNTAX      OCTET STRING
    MAX-ACCESS	read-only
    STATUS		current
    DESCRIPTION
        "The incident's source object type."
    ::= { incidentEventEntry 5 }

incidentSourceObjectID	OBJECT-TYPE
    SYNTAX      OCTET STRING
    MAX-ACCESS	read-only
    STATUS		current
    DESCRIPTION
        "The UUID of the incident's source object."
    ::= { incidentEventEntry 6 }

incidentSourceObjectName	OBJECT-TYPE
    SYNTAX      OCTET STRING
    MAX-ACCESS	read-only
    STATUS		current
    DESCRIPTION
        "The incident's source object name as displayed on the dashboard."
    ::= { incidentEventEntry 7 }

incidentEventType	OBJECT-TYPE
	SYNTAX	    OCTET STRING
    MAX-ACCESS	read-only
    STATUS		current
    DESCRIPTION
        "The type of the event reported."
    ::= { incidentEventEntry 8 }


-- Notification types:

beezAlertNotification NOTIFICATION-TYPE
     OBJECTS { beezAlertID, beezAlertType, beezSourceAlertID, beezAlertTimestamp, beezName, beezID, beezAlertMessage, beezAlertSeverity }
     STATUS       current
     DESCRIPTION
         "A notification about a change in the alert status of a beez agent."
     ::= { nbAlertNotifications 1 }

testAlertNotification NOTIFICATION-TYPE
     OBJECTS { testAlertID,
               testType,
               testAlertSeverity,
               testSourceAlertID,
               testAlertTimestamp,
               testBeezName,
               testBeezID,
               testTargetName,
               testAlertMessage,
               testTargetDisplayName }
     STATUS    current
     DESCRIPTION
         "A notification about a change in the alert status of a monitoring test."
     ::= { nbAlertNotifications 2 }

incidentEventNotification NOTIFICATION-TYPE
    OBJECTS { 	incidentEventID,
              	incidentID,
              	incidentEventMessage,
              	incidentEventTimestamp,
              	incidentSourceObjectType,
              	incidentSourceObjectID,
              	incidentSourceObjectName,
              	incidentEventType }
    STATUS      current
    DESCRIPTION
        "A notification about the change of status of an incident. Either triggered or cleared"
    ::= { nbAlertNotifications 3 }


END
